module tsn-interface-configuration {
  yang-version 1.1;
  namespace "urn:linutronix:tsn-interface-configuration";
  prefix tsn-interface-configuration;

  import ieee802-dot1q-tsn-types {
    prefix tsn;
  }

  description
    "This is only a rudimentary YANG model containing
    the necessary elements for use with the current
    version of the node controller.
    A full model is currently under development as part of 802.1Qcw.";

  container tsn-interface-configuration {
    uses tsn:group-interface-configuration;
  }
}
